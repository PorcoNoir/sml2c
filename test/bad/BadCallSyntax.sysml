package P {
    calc def F {
        in x : Real;
        return r : Real = x;
    }
    part def Q {
        attribute mass : Real;
        // missing )
        attribute bad : Real = F(mass;
    }
}
